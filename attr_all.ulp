#usage "<b><h1>Apply attribute to all package/technology variants</h1></b>\n"
  "<pre><b>attr_all</b> <i>name</i> '<i>value</i>'</pre>"
  "<p>"
  "Sets the indicated attribute for all package and technology combinations of "
  "a device.&nbsp;  This ULP must be run in the device editor of a library."

string fnam;                           //script output file name
string cmd;                            //command to execute at end of ULP
string pack;                           //package variant name string
string techs[];                        //list of technologies
int ntechs;                            //number of technologies in list
int i;                                 //scratch integer and loop counter
//
//   Start of executable program.
//
fnam = argv[0];                        //init temp script name to full ULP pathname
fnam = filesetext (fnam, ".scr");      //make script file of same generic name
output (fnam, "wtD") {                 //open temporary script output file
  deviceset (devset) {
    devset.devices (dev) {

      pack = dev.name;
      if (pack == "''") pack = "";
      printf ("package '%s';\n", pack);

      ntechs = strsplit(techs, dev.technologies, ' ');
      for (i = 0; i < ntechs; i++) {
        printf ("technology %s;\n", techs[i]);
        printf ("attribute %s '%s' constant;\n", argv[1], argv[2]);
        }                              //back for next technology this device
      }                                //back for next DEV in device set
    }                                  //end of device set
  }                                    //done with output file
cmd = "script " + fnam;
exit (cmd);                            //run the temporary script
